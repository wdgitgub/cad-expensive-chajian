(defun c:jt (/ ang h2 jtl oldcm oldos pt1 pt2 pt3 scale)

  (setq oldcm (getvar "cmdecho"))
  (setq oldos (getvar "osmode"))
  (setvar "cmdecho" 0)
  (setvar "osmode" 0)
  (setq scale (getreal "\n请输入比例<100>:"))
  (if (= scale nil)
    (setq scale 100)
  )
  (setq h2 (* 0.8 scale)
	jtl (* 4 scale)
  )
  (setq pt1 (getpoint "\n请输入第一点:"))
  (setq pt3 (getpoint pt1 "\n请输入第二点:"))
  (setq ang (angle pt1 pt3))
  (setq pt2 (polar pt1 ang jtl))
  (command "pline" pt1 "w" 0 h2 pt2 "w" 0 0 pt3)
  (setvar "cmdecho" oldcm)
  (setvar "osmode" oldos)
  (princ "\n  ")
  (princ "\n继续使用pline命令")
  (princ)
)
