(defun c:zstc ( / a b colo ent i laye ss)
  (vl-load-com)
  (princ "\n***>>>>>Welcome to 只刷图层(不刷其他任何特性)<<<<<***\n***>>>>>海盗曹 2014.03.13<<<<<***")
  (setq a (car (entsel "\n选择源对象:")))
  (setq laye (vla-get-layer (vlax-ename->vla-object a)))
  (princ (strcat "\n目标对象图层将被刷为" "【" laye "】"))
  (princ "\n选择目标对象:")
  (setq ss (ssget))
  (repeat (setq i (sslength ss))
    (progn
      (setq b (ssname ss (setq i (1- i))))
      (setq ent (entget b))
      (if (setq colo (cdr (assoc 62 ent)))
	()
	(setq colo (cdr (assoc 62 (tblsearch "layer" (cdr (assoc 8 ent))))))
      )
      (vla-put-layer (vlax-ename->vla-object b) laye)
      (vla-put-color (vlax-ename->vla-object b) colo)
    )
  )
  (princ (strcat "\n所选对象的图层被刷为" "【" laye "】"))
  (princ "\n***>>>>>End of 只刷图层(不刷其他任何特性)<<<<<***")
  (princ)
)

(princ "\n本程序采摘自www.lisp123.com更多内容敬请期待！")
(princ "\n本程序命令：zstc")
(princ)
